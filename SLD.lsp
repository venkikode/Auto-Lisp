(defun dtr(x) (* (/ pi 180.0) x)) 
(defun rtd(x) (* (/ 180 pi) x))
(defun mirr() (command "mirror" "l" "" hc basepoint ""))
(defun mirr1() (command "mirror" "l" "" startpt2 startpt1 "y"))
(defun cen() (command "layer" "s" "cen" ""))  
(defun mem() (command "layer" "s" "mem" ""))  
(defun das() (command "layer" "s" "das" "")) 
(defun hid() (command "chprop" "l" "" "p" "lt" "hidden" ""))
(defun des() (command "layer" "s" "des" ""))  

;;************************ PATTERN LIBRARY **********************************

; ********  X - PATTERNS  ********

(defun eqbeltupdown()
  (setq pt7ref (polar intpt pi bww))
  (setq pt7 (inters pt1 pt5 intpt pt7ref))
  (setq beltn1 (polar pt7 0 (/ (distance pt7 intpt) 2.0)))
  (setq pt8 (polar pt7 0 (* 2.0 (distance pt7 intpt))))
  (des)(command "line" pt7 pt8 "")
  (setq dsttemp (distance pt1 pt7))
  (if (/= bbnd 0)
    (progn
      (setq sldst (/ (distance pt1 pt7) bbnd))
      (setq sldstref sldst)
      (setq ind8 0)
      (repeat (- (+ bbnd abnd) 1)
        (setq ind8 (1+ ind8))
        (if (/= ind8 bbnd) (setq slnod (polar pt1 (angle pt1 pt5) sldst)))
        (if (>= ind8 bbnd) (setq slnod (polar pt7 (angle pt1 pt5) sldst)))
        (if (= ind8 1) (setq sln1 slnod))
        (if (= ind8 2) (setq sln2 slnod))
        (if (= ind8 3) (setq sln3 slnod))
        (if (= ind8 4) (setq sln4 slnod))
        (if (= ind8 5) (setq sln5 slnod))
        (if (= ind8 6) (setq sln6 slnod))
        (if (= ind8 7) (setq sln7 slnod))
        (setq sldst (+ sldst sldstref))
        (if (= ind8 bbnd) 
          (progn
            (setq sldst (/ (distance pt7 pt5) abnd))
            (setq sldstref sldst)
          )
        )
      )
    )
  )
)

(defun changexit () 
  (initget 1 "C X")
  (setq cx (getkword "\nChange / eXit < C / X > :"))
  (if (= cx "X") 
    (progn 
      (setq loop nil index1 nil beltn1 nil mid1 nil mid2 nil mid3 nil ln1 nil
             ln2 nil ln3 nil ln4 nil xbn1 nil xbn2 nil xbn3 nil xbn4 nil
             xtn1 nil xtn2 nil xtn3 nil xtn4 nil xtn5 nil sln1 nil sln2 nil
             sln3 nil sln4 nil an1 nil an2 nil an3 nil an4 nil an5 nil an6 nil
             an7 nil an8 nil an9 nil an10 nil
      )
    )
  )
)




(defun leg2xb0xt0()
  (if (and (and (= ndl 2) (= ndbd 0) (= ndtd 0)))
    (progn 
      (setq loop "XX")
      (setq index1 0)
      (while loop
         (setq index1 (1+ index1))
         (des)
         (if (= index1 1) (progn (command "line" ln1 intpt "")(mirr)))
         (if (= index1 2) (progn (setq abnd 0) (setq bbnd 0) (eqbeltupdown)))
         (prompt "\n2 patterns are available.")
         (changexit)
         (if (= cx "C") (command "undo" "2"))
         (if (= index1 2) (setq index1 0))
      )
    )
  )
)
(defun leg2xb2xt0()
  (if (and (and (= ndl 2) (= ndbd 2) (= ndtd 0)))
    (progn
      (setq abnd 0)
      (setq bbnd 0)
      (eqbeltupdown)
      (command "line" pt7 xbn1 "")(mirr)
    )
  )
)

(defun leg2xb2xt2()
  (if (and (and (= ndbd 2) (= ndtd 2) (= ndl 2)))
    (progn 
      (setq loop "XX")
      (setq index1 0)
      (while loop
        (setq index1 (1+ index1))
        (des) 
        (if (= index1 1) (command "line" xbn1 xtn1 ""))
        (if (= index1 2) (command "line" ln1 intpt ""))
        (mirr)
        (if (/= index1 3)
          (progn
            (command "line" xtn1 ln1 "")(mirr)
            (command "line" ln1 xbn1 "")(mirr)
          )
        )
        (if (= index1 3)
          (progn 
            (setq abnd 0) (setq bbnd 0) (eqbeltupdown)
            (des) (command "line" pt7 xbn1 "")(mirr)
            (command "line" pt7 xtn1 "")(mirr)
          )
        )
        (prompt "\n3 patterns available.")
        (changexit)
        (if (= cx "C") (command "undo" "6"))
        (if (= index1 3) (setq index1 0))
      )
    )
  )
)
(defun leg3xb2xt0()
  (if (and (and (= ndl 3) (= ndbd 2) (= ndtd 0)))
    (progn (setq abnd 0) (setq bbnd 2)(eqbeltupdown)
       (des) (command "line" sln1 xbn1 "")(mirr)
       (command "line" xbn1 pt7 "")(mirr)
    )
  )
)






(defun leg3xb2xt2()
  (if (and (and (= ndl 3) (= ndbd 2) (= ndtd 2)))
    (progn
      (setq loop "XX")
      (setq index1 0)
      (while loop
        (setq index1 (1+ index1))
        (des)
        (if (or (= index1 1) (= index1 3)) (command "line" xbn1 ln2 ""))
        (if (= index1 2) (command "line" xtn1 ln1 ""))
        (mirr)
        (if (= index1 3) (progn (command "line" ln2 intpt "")(mirr)))
        (if (and (/= index1 3) (/= index1 4))
          (progn (command "line" xbn1 xtn1 "")(mirr))
        )
        (if (/= index1 4)
          (progn
            (command "line" ln1 xbn1 "")(mirr)
            (command "line" ln2 xtn1 "")(mirr)
          )
        )
        (if (= index1 4)
          (progn (setq abnd 0) (setq bbnd 2)(eqbeltupdown)
            (des) (command "line" sln1 xbn1 "")(mirr)
            (command "line" xbn1 pt7 "")(mirr)
            (command "line" pt7 xtn1 "")(mirr)
          )
        )
        (prompt "\n4 ptterns available.")
        (changexit)
        (if (= cx "C") (command "undo" "8"))
        (if (= index1 4) (setq index1 0)) 
      )
    )
  )
)
(defun leg3xb3xt2()
  (if (and (and (= ndl 3) (= ndbd 3) (= ndtd 2)))
    (progn
      (setq index1 0)
      (setq loop "XX")
      (while loop
        (setq index1 (1+ index1))
        (if (= index1 1) (command "line" ln1 xbn2 ""))
        (if (= index1 2) (command "line" xbn1 ln2 ""))
        (mirr)
        (des) (command "line" xbn1 ln1 "")(mirr)
        (command "line" xbn2 ln2 "")(mirr)
        (command "line" ln2 xtn1 "")(mirr)
        (command "line" xtn1 xbn2 "")(mirr)
        (prompt "\nAvailable patterns are 2 nos.")        
        (changexit)
        (if (= cx "C") (command "undo" "12"))
        (if (= index1 2) (setq index1 0)) 
      )
    )
  )
)

(defun leg4xb2xt2()
  (if (and (and (= ndl 4) (= ndbd 2) (= ndtd 2)))
    (progn 
      (setq index1 0)
      (setq loop "XX")
      (while loop
        (setq index1 (1+ index1))
        (if (= index1 1)
          (progn
            (des)(command "line" xtn1 ln2 "")(mirr)
            (command "line" xbn1 xtn1 "")(mirr)
          )
        )
        (if (= index1 2)
          (progn
            (setq mid1 (polar ln2 (angle ln2 intpt) (/ (distance ln2 intpt) 2.0)))
            (des)(command "line" ln2 intpt "")(mirr)
            (command "line" ln3 mid1 "")(mirr)
            (command "line" mid1 xtn1 "")(mirr)
          )
        )            
        (if (and (/= index1 3) (/= index1 4))
          (progn
            (command "line" xbn1 ln1 "")(mirr)               
            (command "line" ln2 xbn1 "")(mirr)
            (command "line" xtn1 ln3 "")(mirr)
          )
        )
        (if (or (= index1 3) (= index1 4))
          (progn (setq abnd 2) (setq bbnd 2) (eqbeltupdown)
            (des)(command "line" sln1 xbn1 "")(mirr)
            (command "line" xbn1 pt7 "")(mirr)
            (command "line" xtn1 sln3 "")(mirr)
            (if (= index1 3)
              (progn (command "line" pt7 xtn1 "")(mirr))
              (progn (command "line" xtn1 beltn1 "")(mirr)
                     (command "line" beltn1 sln3 "")(mirr)
              )
            )
          )
        )
        (prompt "\n4 patterns available.")
        (changexit)
        (if (and (= cx "C") (/= index1 3))(command "undo" "12"))
        (if (and (= cx "C") (= index1 3))(command "undo" "10"))
        (if (= index1 4) (setq index1 0)) 
      )
    )
  )
)
(defun leg4xb3xt2()
  (if (and (and (= ndl 4) (= ndbd 3) (= ndtd 2)))
    (progn 
      (setq mid1 (polar xbn2 (angle xbn2 ln2) (/ (distance xbn2 ln2) 2.0)))  
      (setq mid2 (polar ln2 (angle ln2 xtn1) (/ (distance ln2 xtn1) 2.0)))  
      (setq index1 0)
      (setq loop "XX")
      (while loop
        (setq index1 (1+ index1))
        (if (= index1 1) 
          (progn 
            (command "line" ln3 mid2 "")(mirr)
            (command "line" xbn1 mid1 "")(mirr)
            (command "line" ln1 mid1 "")(mirr)
          )
        ) 
        (if (= index1 2) (progn (command "line" xbn1 ln2 "")(mirr)))
        (if (/= index1 3)
          (progn
            (des) (command "line" xbn1 ln1 "")(mirr)
            (command "line" xbn2 ln2 "")(mirr)
            (command "line" ln2 xtn1 "")(mirr)
            (command "line" xbn2 xtn1 "")(mirr)
            (command "line" ln3 xtn1 "")(mirr)
          )
        )
        (if (= index1 3)
          (progn (setq abnd 2)(setq bbnd 2)(eqbeltupdown)
            (des) (command "line" xbn1 sln1 "")(mirr)
            (command "line" sln1 xbn2 "")(mirr)
            (command "line" sln1 beltn1 "")(mirr)
            (command "line" xbn2 beltn1 "")(mirr)
            (command "line" sln3 beltn1 "")(mirr)
            (command "line" beltn1 xtn1 "")(mirr)
            (command "line" sln3 xtn1 "")(mirr)
          )
        )
        (prompt "\n3 patterns available.")
        (changexit)
        (if (= cx "C") (command "undo" "18"))
        (if (= index1 3) (setq index1 0)) 
      )
    )
  )
)
(defun leg4xb4xt2()
  (if (and (and (= ndl 4) (= ndbd 4) (= ndtd 2)))
    (progn
      (setq abnd 2) (setq bbnd 2) (eqbeltupdown)
      (command "line" xbn1 sln1 "")(mirr)
      (command "line" sln1 xbn2 "")(mirr)
      (command "line" xbn2 pt7 "")(mirr)
      (command "line" xbn2 beltn1 "")(mirr)
      (command "line" xbn3 beltn1 "")(mirr)
      (command "line" sln3 xtn1 "")(mirr)
      (command "line" sln3 beltn1 "")(mirr)
      (command "line" xtn1 beltn1 "")(mirr)
    )
  )
)

;***************************************************************************

;********************* A (K) - PATTERNS ************************

(defun leg2a2()
  (if (and (= ndl 2) (= nda 2))
    (progn
      (setq index1 0)
      (setq loop "XX")
      (while loop
        (setq index1 (1+ index1))
        (des)(command "line" an1 ln1 "")(mirr)
        (if (= index1 1)(progn (command "line" ln1 beltn1 "")(mirr)))
        (if (or (= index1 1)(= index1 3))(progn (command "line" beltn1 an1 "")(mirr)))
        (if (or (= index1 2)(= index1 3))(progn (command "line" an1 pt5 "")(mirr)))
        (prompt "\n3 patterns available.")
        (changexit)
        (if (= cx "C") (command "undo" "6"))
        (if (= index1 3) (setq index1 0)) 
      )
    )
  )
)
(defun leg2a3()
  (if (and (= ndl 2) (= nda 3))
    (progn
      (setq index1 0)
      (setq loop "XX")
      (while loop
        (setq index1 (1+ index1))
        (des)(command "line" an1 ln1 "")(mirr)
        (command "line" ln1 an2 "")(mirr)
        (if (= index1 1)(progn (command "line" an2 pt5 "")(mirr)))
        (if (= index1 2)
          (progn 
            (command "line" an2 beltn1 "")(mirr)
            (command "line" ln1 beltn1 "")(mirr)  
          )
        )
        (prompt "\n2 patterns available.")
        (changexit)
        (if (= cx "C") (command "undo" "6"))
        (if (= index1 2) (setq index1 0)) 
      )
    )
  )
)
(defun leg3a3()
  (if (and (= ndl 3) (= nda 3))
    (progn
       (setq index1 0)
       (setq loop "XX")
       (setq extrapt1 (polar ln2 0 (/ (distance ln2 an2) 2.0)))
       (setq extrapt2 (polar an1 (angle an1 pt5) (/ (distance an1 pt5) 2.0)))
       (setq extrapt3 (polar an1 (angle an1 beltn1) (/ (distance an1 beltn1) 2.0)))
       (while loop
         (setq index1 (1+ index1))
         (des) (command "line" ln1 an1 "")(mirr)
         (if (or (or (= index1 1) (= index1 2) (= index1 3)))
           (progn (command "line" an1 ln2 "")(mirr))
         )
         (if (/= index1 5) (progn (command "line" ln2 an2 "")(mirr)))
         (if (= index1 1) (progn (command "line" an2 pt5 "")(mirr)))
         (if (or (= index1 2) (= index1 4)) (progn (command "line" ln2 beltn1 "")(mirr)))
         (if (/= index1 1) (progn (command "line" an2 beltn1 "")(mirr)))
         (if (= index1 3) 
           (progn 
             (command "line" pt5 extrapt1 "")(mirr)
             (command "line" extrapt1 beltn1 "")(mirr)
           )   
         )
         (if (= index1 4)
           (progn
             (command "line" ln1 extrapt1 "")(mirr)
             (command "line" an1 extrapt1 "")(mirr)
           )
         )
         (if (= index1 5)
           (progn
             (command "line" an1 pt5 "")(mirr)
             (command "line" an1 beltn1 "")(mirr)
             (command "line" ln2 extrapt2 "")(mirr)
             (command "line" an2 extrapt3 "")(mirr)
           )
         )
        (prompt "\n5 patterns available.")
        (changexit)
        (if (= cx "C") (command "undo" "10"))
        (if (= index1 5) (setq index1 0)) 
      )
    )
  )
)
(defun leg2a4()
  (if (and (= ndl 2) (= nda 4))
    (progn
      (setq index1 0)
      (setq loop "XX")
      (while loop
        (setq index1 (1+ index1))
        (setq extrapt1 (polar an2 (angle an2 pt5) (/ (distance an2 pt5) 2.0)))
        (setq extrapt2 (polar ln1 (angle ln1 an2) (/ (distance ln1 an2) 2.0)))
        (des)(command "line" an1 ln1 "")(mirr)
        (if (/= index1 4)(progn (command "line" ln1 an2 "")(mirr)))
        (if (/= index1 3)(progn (command "line" an2 pt5 "")(mirr)))
        (command "line" beltn1 an3 "")(mirr)
        (if (= index1 1)
          (progn
            (command "line" extrapt1 an3 "")(mirr)
            (command "line" extrapt1 beltn1 "")(mirr)
          )
        )
        (if (/= index1 1) (progn (command "line" an2 beltn1 "")(mirr))) 
        (if (= index1 3)(progn (command "line" ln1 beltn1 "")(mirr)))
        (if (= index1 4)
          (progn
            (command "line" an1 extrapt1 "") (mirr)
            (command "line" extrapt1 ln1 "")(mirr)
          )
        )
        (if (= index1 5)
          (progn
            (command "line" ln1 extrapt1 "") (mirr)
            (command "line" extrapt1 extrapt2 "")(mirr)
          )
        )
        (prompt "\n5 patterns available.")
        (changexit)
        (if (= cx "C") (command "undo" "10"))
        (if (= index1 5) (setq index1 0)) 
      )
    )
  )
)


(defun settings()
  (setvar "cmdecho" 0)
  (setvar "blipmode" 0)
  (setvar "pdmode" 3)
  (setvar "pdsize" 350)
  (command "viewres" "" "20000")
  (command "layer" "n" "mem,cen,das,des,dim"
                   "c" "4" "mem"
                   "c" "2" "cen" "lt" "center" "cen"
                   "c" "1" "das" "lt" "dashed" "das"
                   "c" "1" "des"
                   "c" "5" "dim" ""
  )
  (command "ltscale" "500")
  (command "style" "standard" "simplex" "250" "" "" "" "" "")
)
(defun x-arms()
  (setq noofarms (getint "\nNo. of X-Arms :"))
  (if (> noofarms 0)
    (progn
      (repeat noofarms
        (initget 1 "E U")
        (setq eu (getkword "\nEqual arms or Unequal arms : < E / U > :"))
        (setq xarmlvl (getdist "\n X-arm level from bottom :")
              xarmbpt (polar basepoint (dtr 90) xarmlvl)
        )
        (if (= eu "E")
           (progn
             (setq xarmlg (getdist "\nX-arm length from center of tower :")
                   xarmlpt (polar xarmbpt pi xarmlg)
                   xarmrpt (polar xarmbpt 0 xarmlg)
             )          
           ) 
           (progn
              (setq xarmlgl (getdist "\nX-arm length from center of tower <LEFT> :")
                    xarmlgr (getdist "\nX-arm length from center of tower <RIGHT> :")
                    xarmlpt (polar xarmbpt pi xarmlgl)
                    xarmrpt (polar xarmbpt 0 xarmlgr)
              )
           )
        )
        (command "line" xarmlpt xarmrpt "")
      )
    )
  )
)

(defun c:tower()
  (settings)
  (graphscr)
  (if (= sp nil) (setq sp '(0.0 0.0 0.0)))
  (setq basepoint sp)
  (if (= noofslps nil) (setq noofslps (getint "\n\n\n\nNo. of slopes :")))
  (prompt "\n\n\n\n********** 1st SLOPE DETAILS **********")
  (if (= bw nil) (setq bw (getdist "\n\nBase width :")))
  (setq bww bw)
  (setq index 0)
  (repeat noofslps
     (setq index (1+ index))
     (if (= index 1) 
       (setq hw (getdist "\n\n\n\n\nHamper width :"))
       (progn
         (princ "\n\n\n\n\n\n\n\n\n\n\n\n\n\n\n\n\n********** Next slope details ***********")
         (setq hw (getdist "\n\nHamper width :"))
       )
     )          
     (setq ht (getdist "\nHeight up to Hamper :")
          pt1 (polar sp pi (/ bw 2.0))
          pt2 (polar sp 0 (/ bw 2.0))
           hc (polar sp (dtr 90) ht)
          pt3 (polar hc 0 (/ hw 2.0))
          pt4 (polar hc pi (/ hw 2.0))
     ) 
     (if (= index 1) (setq 1slope (angle pt1 pt4)))
     (if (= index 2) (setq 2slope (angle pt1 pt4)))
     (if (= index 3) (setq 3slope (angle pt1 pt4)))
     (mem)
     (command "line" pt1 pt2 pt3 pt4 "c")
     (cen)
     ;(command "line" basepoint hc "")
     (command "zoom" "e")
     (command "zoom" "0.9x")
     (setq npanels (getint "\nNo. of panels  :"))
     (graphscr)
        (repeat npanels
           (setq ph (getdist "\nPanel height :")
             pt5ref (polar pt1 (dtr 90) ph)
             pt6ref (polar pt2 (dtr 90) ph)
                pt5 (inters pt1 pt4 pt5ref pt6ref)
                pt6 (inters pt2 pt3 pt5ref pt6ref)
           )
           (initget 1 "X A")
           (setq xva (getkword "\nDiagonals pattern : <X / A> : "))
           (if (= xva "X")
             (progn
               (mem)
               (command "line" pt1 pt6 "")
               (command "line" pt2 pt5 "")
               (setq intpt (inters pt1 pt6 pt2 pt5)
                      ndbd (getint "\nNo. of divisions on bottom diagonal :")
                      ndtd (getint "\nNo. of divisions on top diagonal :")
               )
               (if (> ndbd 0)
                  (progn
                     (setq btdst (/ (distance pt1 intpt) ndbd))
                     (setq btdstref btdst)
                     (setq ind1 0)
                     (repeat (- ndbd 1)
                       (setq ind1 (1+ ind1))
                       (setq bnod (polar pt1 (angle pt1 intpt) btdst))
                       (des)
;                       (command "point" bnod)
                       (if (= ind1 1) (setq xbn1 bnod))
                       (if (= ind1 2) (setq xbn2 bnod))
                       (if (= ind1 3) (setq xbn3 bnod))
                       (setq btdst (+ btdst btdstref))
                     )
                  )
               )
               (if (> ndtd 0)
                  (progn
                     (setq tpdst (/ (distance intpt pt5) ndtd))
                     (setq tpdstref tpdst)
                     (setvar "pdmode" 3)
                     (setvar "pdsize" 350)
                     (setq ind2 0)
                     (repeat (- ndtd 1)
                       (setq ind2 (1+ ind2))
                       (setq tnod (polar intpt (angle intpt pt5) tpdst))
                       (des)
;                       (command "point" tnod)
                       (if (= ind2 1) (setq xtn1 tnod))
                       (if (= ind2 2) (setq xtn2 tnod))
                       (if (= ind2 3) (setq xtn3 tnod))
                       (setq tpdst (+ tpdst tpdstref))
                     )
                  )
               )
             )
           )   
           (if (= xva "A")
             (progn
               (setq apoint (polar pt5 0 (/ (distance pt5 pt6) 2.0)))
               (setq beltn1 (polar pt5 0 (/ (distance pt5 apoint) 2.0)))
               (mem)
               (if (/= (distance pt5 pt4) 0) (command "line" pt5 pt6 ""))
               (command "line" pt1 apoint pt2 "")
               (setq nda (getint "\nNo. of divisions on Lattice :"))
               (if (> nda 0)
                 (progn
                   (setq adst (/ (distance pt1 apoint) nda))
                   (setq adstref adst)
                   (setq ind6 0)
                   (repeat (- nda 1)
                      (setq ind6 (1+ ind6))
                      (setq anod (polar pt1 (angle pt1 apoint) adst))
                      (des)
;                      (command "point" anod)
                      (if (= ind6 1) (setq an1 anod))
                      (if (= ind6 2) (setq an2 anod))
                      (if (= ind6 3) (setq an3 anod))
                      (if (= ind6 4) (setq an4 anod))
                      (if (= ind6 5) (setq an5 anod))
                      (if (= ind6 6) (setq an6 anod))
                      (if (= ind6 7) (setq an7 anod))
                      (if (= ind6 8) (setq an8 anod))
                      (if (= ind6 9) (setq an9 anod))
                      (if (= ind6 10) (setq an10 anod))
                      (setq adst (+ adst adstref))
                   )
                 )
               )
             )
           )
           (setq ndl (getint "\nNo. of divisions on leg :"))
           (if (> ndl 0)
             (progn
                (setq dsttemp (distance pt1 pt5))
                (setq ldst (/ (distance pt1 pt5) ndl))
                (setq ldstref ldst)
                (setq ind3 0)
                (repeat (- ndl 1)
                  (setq ind3 (1+ ind3))
                  (setq lnod (polar pt1 (angle pt1 pt5) ldst))
                  (des)
;                  (command "point" lnod)
                  (if (= ind3 1) (setq ln1 lnod))
                  (if (= ind3 2) (setq ln2 lnod))
                  (if (= ind3 3) (setq ln3 lnod))
                  (if (= ind3 4) (setq ln4 lnod))
                  (if (= ind3 5) (setq ln5 lnod))
                  (if (= ind3 6) (setq ln6 lnod))
                  (if (= ind3 7) (setq ln7 lnod))
                  (if (= ind3 8) (setq ln8 lnod))
                  (if (= ind3 9) (setq ln9 lnod))
                  (if (= ind3 10) (setq ln10 lnod))
                  (setq ldst (+ ldst ldstref))
                )
             )
           )
           (if (= xva "X")(leg2xb0xt0))
           (if (= xva "X") (leg2xb2xt0))
           (if (= xva "X") (leg2xb2xt2))
           (if (= xva "X") (leg3xb2xt0))
           (if (= xva "X") (leg3xb2xt2))
           (if (= xva "X") (leg3xb3xt2))
           (if (= xva "X") (leg4xb2xt2))
           (if (= xva "X") (leg4xb3xt2))
           (if (= xva "X") (leg4xb4xt2))
           (if (= xva "A") (leg2a2))
           (if (= xva "A") (leg2a3))
           (if (= xva "A") (leg2a4))
           (if (= xva "A") (leg3a3))

 
           (setq pt1 pt5)
           (setq pt2 pt6)
           (setq sp (polar sp (dtr 90) ph))
        )
        (setq sp hc)
        (setq bw hw)
        (princ)
  )
;  (x-arms) 
)

; ********************   B O D Y   E X T E N S I O N   *******************
(defun c:body()
  (settings)
  (prompt "\n\n\n\n** SLOPE DETAILS **")
  (setq sp (getpoint "\nStart point :"))
  (textscr)
  (prompt "\n\n\n\n\n\n\n\n\n\n\n\n\n\n\n\n\n\n\n\n\n\n\nPress return for default base width =")
  (print bww)
  (setq bww1 nil)
  (setq bww1 (getdist "\nBase width : < Default >"))
  (if (= bww1 nil) (setq bww1 bww) (setq bww bww1))
  (setq ht (getdist "\nBody height :")
       pt1 (polar sp pi (/ bww 2.0))
       pt4 (polar sp 0 (/ bww 2.0))     
       hc (polar sp (dtr 270) ht)
       hyp (/ ht (sin 1slope))
       pt2 (polar pt1 (+ pi 1slope) hyp)
 pt3refdst (distance pt2 hc)
      pt3 (polar hc 0 pt3refdst)
  )
  (mem)
  (command "line" pt1 pt2 pt3 pt4 "c")
  (textscr)
  (setq npanels (getint "\nNo. of panels  :"))
  (graphscr)
  (if (> npanels 0)
    (progn
      (repeat npanels
        (setq ph (getdist "\nPanel height :")
          pt5ref (polar pt2 (dtr 90) ph)
          pt6ref (polar pt3 (dtr 90) ph)
             pt5 (inters pt2 pt1 pt5ref pt6ref)
             pt6 (inters pt3 pt4 pt5ref pt6ref)
        )
        (initget 1 "X V A")
        (setq xva (getkword "\nDiagonals pattern : <X / V / A> : "))
        (if (= xva "X")   
           (progn
             (mem)
             (command "line" pt2 pt6 "")
             (command "line" pt3 pt5 "")
             (setq intpt (inters pt2 pt6 pt3 pt5)
                    ndbd (getint "\nNo. of divisions on bottom diagonal :")
                    ndtd (getint "\nNo. of divisions on top diagonal :")
             )
             (if (> ndbd 0)
                (progn
                   (setq btdst (/ (distance pt2 intpt) ndbd))
                   (setq btdstref btdst)
                   (setvar "pdmode" 3)
                   (setvar "pdsize" 350)
                   (repeat (- ndbd 1)
                     (setq bnod (polar pt2 (angle pt2 intpt) btdst))
                     (des)
;                     (command "point" bnod)
                     (setq btdst (+ btdst btdstref))
                   )
                )
             )
             (if (> ndtd 0)
                (progn
                   (setq tpdst (/ (distance intpt pt5) ndtd))
                   (setq tpdstref tpdst)
                   (setvar "pdmode" 3)
                   (setvar "pdsize" 350)
                   (repeat (- ndtd 1)
                     (setq tnod (polar intpt (angle intpt pt5) tpdst))
                     (des)
;                     (command "point" tnod)
                     (setq tpdst (+ tpdst tpdstref))
                   )
                )
             )
           )
        )
        (if (= xva "V")
          (progn
            (mem)
            (command "line" pt5 hc pt6 "")
            (setq ndv (getint "\nNo. of divisions on V :"))
            (if (> ndv 0)
              (progn
                (setq vdst (/ (distance hc pt5) ndv))
                (setq vdstref vdst)
                (repeat (- ndv 1)
                  (setq vnod (polar hc (angle hc pt5) vdst))
                  (des)
;                  (command "point" vnod)
                  (setq vdst (+ vdst vdstref))
                )
              )
            )
          )
        )
        (if (= xva "A")
           (progn
             (setq apoint (polar pt5 0 (/ (distance pt5 pt6) 2.0)))
             (mem)
             (command "line" pt2 apoint pt3 "")
             (setq nda (getint "\nNo. of divisions on A :"))
             (if (> nda 0)
               (progn
                 (setq adst (/ (distance pt2 apoint) nda))
                 (setq adstref adst)
                 (repeat (- nda 1)
                    (setq anod (polar pt2 (angle pt2 apoint) adst))
                    (des)
;                    (command "point" anod)
                    (setq adst (+ adst adstref))
                 )
               )
             )
           )
        )
        (setq ndl (getint "\nNo. of divisions on leg :"))
        (if (> ndl 0)
          (progn
             (setq ldst (/ (distance pt2 pt5) ndl))
             (setq ldstref ldst)
             (repeat (- ndl 1)
               (setq lnod (polar pt2 (angle pt2 pt5) ldst))
               (des)
;               (command "point" lnod)
               (setq ldst (+ ldst ldstref))
             )
          )
        )
        (setq pt2 pt5)
        (setq pt3 pt6)
        (setq hc (polar hc (dtr 90) ph))
      )
    )
  )
)
;*************************** L E G  E X T E N S I O N *************************
(defun c:leg()
  (settings)
  (setq sp (getpoint "\nStart point :"))
  (textscr)
  (prompt "\n\n\n\n\n\n\n\n\n\n\n\n\n\n\n\n\n\n\n\n\n\n\nPress return for default base width =")
  (print bww)
  (setq bww1 nil)
  (setq bww1 (getdist "\nBase width : < Default >"))
  (if (= bww1 nil) (setq bww1 bww) (setq bww bww1))
  (setq lht (getdist "\n Leg height :"))
  (initget 1 "L R")
  (setq lr (getkword "\nTo be placed at left side or right side  : < L / R > : "))
  (setq npl (getint "\nNumber of divisions on lattice  :"))
  (setq npleg (getint "\nNumber of divisions on leg  :"))
 
  (setq hlc (polar sp (dtr 270) lht)
        hyp (/ lht (sin 1slope))
  )
  (if (= lr "L")
    (progn
     (setq plt1 (polar sp pi (/ bww 2.0)))
     (setq plt2 (polar plt1 (+ pi 1slope) hyp))
    )
  )
  (if (= lr "R")
     (progn
       (setq plt1 (polar sp 0 (/ bww 2.0)))
       (setq plt2 (polar plt1 (- (dtr 360) 1slope) hyp))
     )
  )  
  (mem)
  (command "line" plt1 sp plt2 "c")
  (if (> npl 0)
     (progn
        (setq leglatdst (/ (distance plt2 sp) npl))
        (setq leglatdstref leglatdst)
        (repeat (- npl 1)
           (setq leglatnod (polar plt2 (angle plt2 sp) leglatdst))
           (des)
;           (command "point" leglatnod)
           (setq leglatdst (+ leglatdst leglatdstref))
        )
     )
  )
  (if (> npleg 0)
     (progn
        (setq legeqdst (/ (distance plt2 plt1) npleg))
        (setq legeqdstref legeqdst)
        (repeat (- npleg 1)
           (setq legnod (polar plt2 (angle plt2 plt1) legeqdst))
           (des)
;           (command "point" legnod)
           (setq legeqdst (+ legeqdst legeqdstref))
        )
     )
  )
)
(defun c:clear()
  (setq bp (getpoint "\nStart point :"))
  (textscr)
  (initget 1 "S T")
  (setq st (getkword "\n\n\n\n\n\n\n\n\n\n\n\n\n\n\n\n\n\n\n\n\n\n\n\n\nSuspension tower / Tension tower : < S / T > :"))
  (if (= st "S")
    (progn
       (initget 1 "L R")
       (setq lrarm (getkword "\nLeft X-arm or Right X-Arm : < L / R > :"))
       (setq hangerlg (getdist "\n\nHanger length :")
               insulg (getdist "\nInsulator length :")
              archorn (getdist "\nArching horn distance :")
       )
       (textscr)
       (prompt "\n\n\n\n\n\n\n\n\n\n\n\n\n\n\n\n\n\n\n\n\n\n\n\nType `0' - In case of no conductor drop")
       (setq condrop (getdist "\n\nConductor drop length :")
            bundlesp (getdist "\nBundle spacing :")
              swings (getint "\nNo. of swings :")
               hiint (polar bp (dtr 270) hangerlg)
       )
       (setq a 0)
       (repeat swings
           (setq a (+ a 1))
           (setq sa (getdist "\n\n\n\nSwing angle :"))
           (setq dimsa sa)
           (if (= lrarm "L") (setq sa (dtr (+ sa 270))))
           (if (= lrarm "R") (setq sa (dtr (- 270 sa))))
           (setq  clears (getdist "\nClearance distance :")
                  insupt (polar hiint sa insulg)
                 inscdpt (polar insupt sa condrop)
                      d1 (polar inscdpt (- sa (dtr 90)) (/ bundlesp 2.0))
                      d2 (polar inscdpt (+ sa (dtr 90)) (/ bundlesp 2.0))
                      d3 (polar hiint sa archorn)
           )
           (if (= lrarm "L") 
             (progn
                (setq arcpt (polar d2 (- sa (dtr 20)) clears))
                (setq leapt (polar d2 (+ sa (dtr 12.5)) clears))
                (setq dimpt (polar d3 (dtr 90) clears))
                (setq verdimpt (polar bp pi 3000))
             )
           )
           (if (= lrarm "R") 
              (progn
                 (setq arcpt (polar d1 (- sa (dtr 40)) clears))
                 (setq leapt (polar d1 (- sa (dtr 12.5)) clears))
                 (setq dimpt (polar d3 (dtr 90) clears))
                 (setq verdimpt (polar bp 0 3000))
              )
          )
          (mem)
          (command "line" bp hiint "")
         
          (if (> condrop 0) 
                      (progn		(mem)
            (command "line" hiint insupt inscdpt "")
            (command "line" hiint insupt "")
          ))
          (command "units" "" "" "" "0" "" "")
          (setvar "dimasz" 0)
          (setvar "dimtsz" 0.5)
          (if (= a 1) 
            (progn
              (setq dimsa1 dimsa)
              (setq angdimpt1 (polar hiint (angle hiint insupt) (/ (distance hiint insupt) 2.0)))
            )
          ) 
          (if (= a 2) 
            (progn
              (setq dimsa2 (+ dimsa dimsa1))
              (setq angdimpt2 (polar hiint (angle hiint insupt) (/ (distance hiint insupt) 2.0)))
              (dim)
              (command "dim1" "ang" angdimpt1 angdimpt2 "@" "" "")              
            )
          ) 
          (if (= a 3) 
            (progn
              (setq dimsa3 (+ dimsa dimsa2))
              (setq angdimpt3 (polar hiint (angle hiint insupt) (/ (distance hiint insupt) 2.0)))
              (dim)
              (command "dim1" "ang" angdimpt1 angdimpt3 "@" (fix dimsa3) "@")              
            )
          ) 
          (if (= a 4) 
            (progn
              (setq dimsa4 (+ dimsa dimsa3))
              (setq angdimpt4 (polar hiint (angle hiint insupt) (/ (distance hiint insupt) 2.0)))
              (command "dim1" "ang" angdimpt1 angdimpt4 "@" (fix dimsa4) "@")
            ) 
          )
          (des)
          (command "donut" "0" "100" d1 d2 d3 "")
          (if (= lrarm "L") (command "arc" "c" d2 arcpt "a" "65"))
          (if (= lrarm "R") (command "arc" "c" d1 arcpt "a" "65"))
          (if (= a swings) 
             (progn
               (setq arcpt1 (polar d3 (dtr 125) clears))
               (command "arc" "c" d3 arcpt1 "a" "-80")
               (setvar "dimtsz" 0)
               (setvar "dimasz" 2)
               (dim)
               (command "dim1" "rad" dimpt (fix clears))
             )
          ) 
          (setvar "dimtix" 1)
          (setvar "dimtad" 1)
          (setvar "dimtsz" 0)
          (setvar "dimasz" 2)
          (command "dim1" "rad" leapt (fix clears))
          (if (= a 1) 
            (progn
              (setq hiint1 hiint)
              (setq insupt1 insupt)
              (setq inscdpt1 inscdpt)
            )
          )
       )
       (setvar "dimasz" 0)
       (setvar "dimtsz" 0.5)
       (setvar "dimtofl" 1)
       (setvar "dimtix" 0)
       (setvar "dimexo" 2)
       (dim)
       (command "dim1" "ver" hiint1 bp verdimpt (fix hangerlg))
       (des)
       (command "text" (polar bp (dtr 175.8) 2406.5) "90" "HANGER")
       (setvar "dimtix" 1)
       (dim)
       (command "dim1" "ver" hiint1 insupt1 verdimpt (fix insulg))
       (setq reftxtpt1 (polar verdimpt (dtr 270) (+ hangerlg (/ insulg 2.0))))
       (setq txtpt1 (polar reftxtpt1 0 600))
       (setq txtpt2 (polar txtpt1 0 686))
       (des)
       (command "text" "c" txtpt1 "90" "INSULATOR")
       (command "text" "c" txtpt2 "90" "LENGTH")
       (if (> condrop 0) 
         (progn
           (setvar "dimtix" 0)
           (setq txtpt3 (polar txtpt1 (dtr 270) (+ (/ insulg 2.0) condrop 1000)))
           (setq txtpt4 (polar txtpt2 (dtr 270) (+ (/ insulg 2.0) condrop 1000)))
           (dim)
           (command "dim1" "ver" insupt1 inscdpt1 verdimpt (fix condrop))
           (des)
           (command "text" "c" txtpt3 "90" "COND.")
           (command "text" "c" txtpt4 "90" "DROP")
         )
       )
    )
  )
)
(defun c:ttt()
(setvar "cmdecho" 1)
(defun DTR(x) (* (/ pi 180.0) x))
(command "ltscale" 400)
(command "dimasz" 25)
(command "dimtsz" 25)
(command "dimexe" 25)
(command "dimexo" 5)
(command "dimlwd" 9)
(command "dimlwe" 9)
(command "dimgap" 1)
(command "dimtad" 1)
(command "dimtofl" 1)
(command "dimtih" 0)
(command "dimtoh" 0)
(if (and (> tower_hight 5000) (<= tower_hight 20000)) (progn (command "style" "standard" "simplex" 180 "0.8" "" "" "" "") (setq vv 180) (command "dimtxt" 180) (setq tab1 (polar basepoint (DTR 180.0) (+ (/ bww 2) 3000)))  (setq tab2 (polar tab1 (DTR 180.0) 1000)) (setq tab3 (polar tab2 (DTR 180.0) 1000)) (setq tab4 (polar tab3 (DTR 180.0) 1000)) (setq tab5 (polar tab4 (DTR 180.0) 800)) ))
(if (and (> tower_hight 20000) (<= tower_hight 40000)) (progn (command "style" "standard" "simplex" 250 "0.8" "" "" "" "") (setq vv 250) (command "dimtxt" 250) (setq tab1 (polar basepoint (DTR 180.0) (+ (/ bww 2) 3000)))  (setq tab2 (polar tab1 (DTR 180.0) 1050)) (setq tab3 (polar tab2 (DTR 180.0) 1050)) (setq tab4 (polar tab3 (DTR 180.0) 1050)) (setq tab5 (polar tab4 (DTR 180.0) 950)) ))
(if (and (> tower_hight 40000) (<= tower_hight 60000)) (progn (command "style" "standard" "simplex" 300 "0.8" "" "" "" "") (setq vv 300) (command "dimtxt" 300) (setq tab1 (polar basepoint (DTR 180.0) (+ (/ bww 2) 3000)))  (setq tab2 (polar tab1 (DTR 180.0) 1100)) (setq tab3 (polar tab2 (DTR 180.0) 1100)) (setq tab4 (polar tab3 (DTR 180.0) 1100)) (setq tab5 (polar tab4 (DTR 180.0) 1000)) ))
(if (and (> tower_hight 60000) (<= tower_hight 80000)) (progn (command "style" "standard" "simplex" 350 "0.8" "" "" "" "") (setq vv 350) (command "dimtxt" 350) (setq tab1 (polar basepoint (DTR 180.0) (+ (/ bww 2) 3000)))  (setq tab2 (polar tab1 (DTR 180.0) 1150)) (setq tab3 (polar tab2 (DTR 180.0) 1150)) (setq tab4 (polar tab3 (DTR 180.0) 1150)) (setq tab5 (polar tab4 (DTR 180.0) 1050)) ))
(if (and (> tower_hight 80000) (<= tower_hight 90000)) (progn (command "style" "standard" "simplex" 400 "0.8" "" "" "" "") (setq vv 400) (command "dimtxt" 400) (setq tab1 (polar basepoint (DTR 180.0) (+ (/ bww 2) 3000)))  (setq tab2 (polar tab1 (DTR 180.0) 1250)) (setq tab3 (polar tab2 (DTR 180.0) 1250)) (setq tab4 (polar tab3 (DTR 180.0) 1250)) (setq tab5 (polar tab4 (DTR 180.0) 1150)) ))
(setq tab_end1 (polar tab1 (DTR 270.0) 3500))
(setq tab_end2 (polar tab5 (DTR 270.0) 3500))
(command "line" tab1 (polar tab1 (DTR 270.0) 3500) "")
(command "line" tab2 (polar tab2 (DTR 270.0) 3500) "")
(command "line" tab3 (polar tab3 (DTR 270.0) 3500) "")
(command "line" tab4 (polar tab4 (DTR 270.0) 3500) "")
(command "line" tab5 (polar tab5 (DTR 270.0) 3500) "")
(command "line" tab_end1 tab_end2 "")
(command "line" tab1 tab5 "")
(command "TEXT" (polar tab5 (DTR 280.0) 3230) "90" "PANEL No.S")
(command "TEXT" (polar tab4 (DTR 280.0) 3245) "90" "MAIN LEGS")
(command "TEXT" (polar tab3 (DTR 280.0) 3245) "90" "DIAGONALS")
(command "TEXT" (polar tab2 (DTR 280.0) 3245) "90" "HORIZONTALS")
(setq dime_start (polar basepoint (DTR 180.0) (+ (/ bww 2) 800)))
(setq index 0)
(setq st dime_start)
(repeat npanelss
(setq index (1+ index))
(setq dis (eval (read (strcat "pnum" (rtos index 2 0)))))
(setq end (polar st (DTR 90.0) dis))
(setq tab1_end (polar tab1 (DTR 90.0) dis))
(setq tab2_end (polar tab2 (DTR 90.0) dis))
(setq tab3_end (polar tab3 (DTR 90.0) dis))
(setq tab4_end (polar tab4 (DTR 90.0) dis))
(setq tab5_end (polar tab5 (DTR 90.0) dis))
(command "dim1" "ver" st end (polar st (DTR 180.0) 1000) dis) 
(command "line" tab1 tab1_end "") 
(command "line" tab2 tab2_end "") 
(command "line" tab3 tab3_end "") 
(command "line" tab4 tab4_end "")
(command "line" tab5 tab5_end "")
(command "line" tab1_end tab5_end "")
(setq pnum (polar tab5_end (DTR 0.0) (* (distance tab5 tab4) 0.7)))
(command "TEXT" (polar pnum (DTR 270.0) (/ dis 2)) "90" index)
(setq t_1 (eval (read (strcat "t" (rtos index 2 0)))))
(setq t_2 (eval (read (strcat "t" (rtos index 2 0) "_1" ))))
(setq t_3 (eval (read (strcat "tt" (rtos index 2 0)))))
(setq t_4 (eval (read (strcat "tt" (rtos index 2 0) "_1" ))))
(setq t_5 (eval (read (strcat "ttt" (rtos index 2 0)))))
(setq t_6 (eval (read (strcat "ttt" (rtos index 2 0) "_1" ))))
(if (= vv 180) (progn (setq cl1 (/ (- dis 1300) 2)) (setq cl2 (/ (- dis 1000) 2)) (setq cl3 (/ (- dis 700) 2))))
(if (= vv 250) (progn (setq cl1 (/ (- dis 2032) 2)) (setq cl2 (/ (- dis 1521) 2)) (setq cl3 (/ (- dis 953) 2))))
(if (= vv 300) (progn (setq cl1 (/ (- dis 2435) 2)) (setq cl2 (/ (- dis 1829) 2)) (setq cl3 (/ (- dis 1151) 2))))
(if (= vv 400) (progn (setq cl1 (/ (- dis 3246) 2)) (setq cl2 (/ (- dis 2439) 2)) (setq cl3 (/ (- dis 1529) 2))))
(setq tmp1 (polar tab4 (DTR 0.0) (* (/ (distance tab3 tab4) 2) 0.75)))
(setq tmp2 (polar tab4 (DTR 0.0) (* (distance tab3 tab4) 0.8)))
(command "TEXT" (polar tmp1 (DTR 90.0) cl1) "90" t_1)
(command "TEXT" (polar tmp2 (DTR 90.0) cl2) "90" t_2)
(setq tmp3 (polar tab3 (DTR 0.0) (* (/ (distance tab3 tab2) 2) 0.75)))
(setq tmp4 (polar tab3 (DTR 0.0) (* (distance tab3 tab2)  0.8)))
(command "TEXT" (polar tmp3 (DTR 90.0) cl1) "90" t_3)
(command "TEXT" (polar tmp4 (DTR 90.0) cl3) "90" t_4)
(setq tmp5 (polar tab2 (DTR 0.0) (* (/ (distance tab2 tab1) 2) 0.75)))
(setq tmp6 (polar tab2 (DTR 0.0) (* (distance tab2 tab1) 0.8)))
(command "TEXT" (polar tmp5 (DTR 90.0) cl1) "90" t_5)
(command "TEXT" (polar tmp6 (DTR 90.0) cl3) "90" t_6)
(setq st end)
(setq tab1 tab1_end)
(setq tab2 tab2_end)
(setq tab3 tab3_end)
(setq tab4 tab4_end)
(setq tab5 tab5_end)
)
(command "dim1" "ver" dime_start st (polar st (DTR 180.0) 1500) (strcat (rtos(/ tower_hight 1000) 2 0) " Tower"))
(command "dim1" "hor" pt1 pt2 (polar pt1 (DTR 90.0) 500) tower_top)
(setq ptm1 (polar basepoint (DTR 180.0) (/ bww 2)))
(setq ptm2 (polar basepoint (DTR 0.0) (/ bww 2)))
(command "dim1" "hor" ptm1 ptm2 (polar ptm1 (DTR 270.0) 500) bww)
(command "TEXT" "J" "C" (polar basepoint (DTR 270.0) 1200) "0" "%%UEXISTING TOWER")
(command "TEXT" "J" "C" (polar basepoint (DTR 270.0) 1600) "0" (strcat "%%UDESIGN NAME:" designname))

(setq pltt1_temp (polar basepoint (DTR 270.0) 4000))
(setq pltt1 (polar pltt1_temp (DTR 0.0) bww))
(setq pltt2_temp (polar tab5_end (DTR 90.0) 1000))
(setq pltt2 (polar pltt2_temp (DTR 180.0) 1000))
(ptts)
(command "QUIT" "Y" "")
)
