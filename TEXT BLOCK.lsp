(defun c:tob (/ a ts n index b1 b c d b2)
   (setvar "osmode" 0)
   (setvar "cmdecho" 0)
   (setq a (ssget))
   (setq n (sslength a))
   (setq index 0 )
   (initget 1 "Y N")
   (setq dell (getkword "\nDo you want to delete all sorce objects <Yes/No>::"))
   (repeat n
      (setq b1 (entget (ssname a index)))
      (setq index (1+ index))
      (setq b (assoc 0 b1 ))
      (if (= "TEXT" (cdr b))
	 (progn
	    (setq aa (cdr (assoc 1 b1 )))
	    (setq p1 (cdr (assoc 10 b1 )))
		(setq numlength (strlen aa))
		(if (= numlength 1) (command "_insert" "f2" p1 "" "" "" aa ""))
		(if (= numlength 2) (command "_insert" "f2" p1 "" "" "" aa ""))
		(if (= numlength 3) (command "_insert" "f3" p1 "" "" "" aa ""))
		(if (= numlength 4) (command "_insert" "f4" p1 "" "" "" aa ""))
		(if (= numlength 5) (command "_insert" "f5" p1 "" "" "" aa ""))
		(if (= numlength 6) (command "_insert" "f6" p1 "" "" "" aa ""))
	 )
      )
   )
   (if (= dell "Y") (command "erase" "p" ""))
(setvar "osmode" 111)
(princ)
)
