(setq plotsty "rccdwg.ctb")
(defun dtr(x) (* (/ pi 180.0) x))
(defun rtd(x) (* (/ 180 pi) x))

(defun c:member()
 (setq a (ssget))
   (setq n (sslength a))
   (setq index 0 )
   (setq v1 (getpoint "\npick the point to generate members: "))
   (setq letter (getstring "\n ENTER the member starting Letter"))
   (repeat n
      (setq bb1 (entget (ssname a index)))
      (setq index (1+ index))
      (setq bb (assoc 0 bb1 ))

 (defun memb()
 (setq v2 (polar v1 (DTR 0.0) 1400))
 (setq v3 (polar v2 (DTR 90.0) 140))
 (setq v4 (polar v3 (DTR 180.0) 1400))
 (setq ufc1 (polar v1 (DTR 90.0) 70))
 (setq ufc2 (polar v2 (DTR 90.0) 70))
 (setq uft1 (polar v1 (DTR 90.0) 10))
 (setq uft2 (polar v2 (DTR 90.0) 10))

 (setq v5 (polar v1 (DTR 270.0) 100))

  (setq v6 (polar v5 (DTR 0.0) 1400))
 (setq v7 (polar v6 (DTR 270.0) 140))
 (setq v8 (polar v7 (DTR 180.0) 1400))
 (setq lfc1 (polar v5 (DTR 270.0) 70))
 (setq lfc2 (polar v6 (DTR 270.0) 70))
 (setq lft1 (polar v5 (DTR 270.0) 10))
 (setq lft2 (polar v6 (DTR 270.0) 10))

 (setq b1 (polar lfc1 (DTR 0.0) 100))
 (setq b2 (polar lfc2 (DTR 180.0) 100))
 (setq dpv (polar v8 (DTR 270.0) 100))
 (setq dph (polar v5 (DTR 180.0) 100))
 (setq dptemp (polar v8 (DTR 270.0) 250))
 (setq dp (polar dptemp (DTR 0.0) 450))

 (setq d1 (polar b1 (DTR 270.0) 70))
 (setq d2 (polar b2 (DTR 270.0) 70))


(defun mem() (command "layer" "s" "mem" ""))
(defun cen() (command "layer" "s" "cen" ""))
(defun das() (command "layer" "s" "das" ""))
(defun dim() (command "layer" "s" "dim" ""))
(defun des() (command "layer" "s" "des" ""))
(defun bolt() (command "layer" "s" "bolt" ""))
;for zoom 
 (setq zt1 (polar v4 (DTR 180.0) 200))
 (setq zt2 (polar zt1 (DTR 90.0) 200))
 (setq zt3 (polar v8 (DTR 270.0) 300))
 (setq zt4 (polar zt3 (DTR 0.0) 1500))
 
(command "_zoom" "w" zt2 zt4 "")
 (mem)(command "line" v1 v2 v3 v4 v1 "") (command "line" v5 v6 v7 v8 v5 "")
 ;(cen)(command "line" ufc1 ufc2 "")  ;upper flang center
 (cen)(command "line" lfc1 lfc2 "") ;lower flang center
 (das)(command "line" uft1 uft2 "") (command "line" lft1 lft2 "")
 (bolt) (command "_insert" "16c" b1 "2.5" "" "90" "") (command "_insert" "16c" b2 "2.5" "" "90" "")

(dim)(command "dim1" "hor" v8 d1 dpv "25" "")
(dim)(command "dim1" "hor" d1 d2 dpv di "")
 (dim) (command "dim1" "hor" d2 v7 dpv "25" "")
  (dim)(command "dim1" "ver" v5 lfc1 dph "23" "")

  (setq nn index)
  (setq numb (strcat letter (itoa nn )))

(setq k2 "L45x45x5")
(setq ptcoord (strcat k2 "..." (itoa dii ) ".Lg." ))
(if (= (strlen numb) 2) (command "_insert" "f2x" dp "" "" "" numb ptcoord "") )
(if (= (strlen numb) 3) (command "_insert" "f3x" dp "" "" "" numb ptcoord "") )
(if (= (strlen numb) 4) (command "_insert" "f4x" dp "" "" "" numb ptcoord "") )


(setq next (polar v8 (DTR 270.0) 450))
(setq nxtemp1 (polar v8 (DTR 0.0) 1800))
(setq next1 (polar nxtemp1 (DTR 90.0) 5070))
(if (= (strlen numb) 2) (progn (setq v9 (polar dp (DTR 0.0) 81.1)) (setq v10 (polar v9 (DTR 90.0) 15)) (setq v11 (polar v10 (DTR 0.0) 460)) ))
(if (= (strlen numb) 3) (progn (setq v9 (polar dp (DTR 0.0) 118.8)) (setq v10 (polar v9 (DTR 90.0) 15)) (setq v11 (polar v10 (DTR 0.0) 460)) ))
(if (= (strlen numb) 4) (progn (setq v9 (polar dp (DTR 0.0) 148.8)) (setq v10 (polar v9 (DTR 90.0) 15)) (setq v11 (polar v10 (DTR 0.0) 460)) ))
(des)(command "line" v10 v11 "")
(if (< index 8) (setq v1 next))
(if (= index 8) (setq v1 next1))
(if ( and (> index 8)(< index 16)) (setq v1 next))
(if (= index 16) (setq v1 next1))
(if ( and (> index 16)(< index 24)) (setq v1 next))
(if (= index 24) (setq v1 next1))
(if ( and (> index 24)(< index 32)) (setq v1 next))
(if (= index 32) (setq v1 next1))
(if ( and (> index 32)(< index 40)) (setq v1 next))
(if (= index 40) (setq v1 next1))
(if ( and (> index 40)(< index 48)) (setq v1 next))
(if (= index 48) (setq v1 next1))
(if ( and (> index 48)(< index 56)) (setq v1 next))
(if (= index 56) (setq v1 next1))
(if ( and (> index 56)(< index 64)) (setq v1 next))
(if (= index 64) (setq v1 next1))
(if ( and (> index 64)(< index 72)) (setq v1 next))
(if (= index 72) (setq v1 next1))
(if ( and (> index 72)(< index 80)) (setq v1 next))
(if (= index 80) (setq v1 next1))
(if ( and (> index 80)(< index 88)) (setq v1 next))
(if (= index 88) (setq v1 next1))
(if ( and (> index 88)(< index 96)) (setq v1 next))
(if (= index 96) (setq v1 next1))
(if ( and (> index 96)(< index 104)) (setq v1 next))
(if (= index 104) (setq v1 next1))
(if ( and (> index 104)(< index 112)) (setq v1 next))
(if (= index 112) (setq v1 next1))
(if ( and (> index 112)(< index 120)) (setq v1 next))
(if (= index 120) (setq v1 next1))
(if ( and (> index 128)(< index 136)) (setq v1 next))
(if (= index 136) (setq v1 next1))
(if ( and (> index 136)(< index 144)) (setq v1 next))
(if (= index 144) (setq v1 next1))
(if ( and (> index 144)(< index 152)) (setq v1 next))
(if (= index 152) (setq v1 next1))
(if ( and (> index 152)(< index 160)) (setq v1 next))
(if (= index 160) (setq v1 next1))
(if ( and (> index 160)(< index 168)) (setq v1 next))
(if (= index 168) (setq v1 next1))
(if ( and (> index 168)(< index 176)) (setq v1 next))
(if (= index 176) (setq v1 next1))
(if ( and (> index 176)(< index 184)) (setq v1 next))
(if (= index 184) (setq v1 next1))
(if ( and (> index 184)(< index 192)) (setq v1 next))
(if (= index 192) (setq v1 next1))
(if ( and (> index 192)(< index 200)) (setq v1 next))
)

(if (or (= "LINE" (cdr bb)) (= "LWPOLYLINE" (cdr bb)))
	 (progn
	    (setq c (assoc 10 bb1 ))
		(setq cc (assoc 11 bb1 ))
		(setq p2 (cdr c))
        (setq p3 (cdr cc))
		(setq p4 (distance p2 p3))
		(setq di (fix p4))
		(setq dii (+ di 50))

		(setq ang (angle p2 p3))
		(setq p5 (/ di 2))
		(setq p6 (polar p2 (angle p2 p3) p5))
		(setq p7 (polar p6 (+ ang (dtr 90.0)) 20))
		(if (< (rtd ang) 90) (setq angg (- (rtd ang) 360)))
        (if (> (rtd ang) 90) (setq angg (- (rtd ang) 180)))
		(setq nn index)
        (setq numb1 (strcat letter (itoa nn )))
		(if (= (strlen numb1) 2) (command "_insert" "f2" P7 "" "" angg numb1 "") )
		(if (= (strlen numb1) 3) (command "_insert" "f3" P7 "" "" angg numb1 "") )
		(if (= (strlen numb1) 4) (command "_insert" "f4" P7 "" "" angg numb1 "") )

		(memb)
		))
	 (if (or (= "TEXT" (cdr bb)) (= "MTEXT" (cdr bb)))
	 (progn
	    (setq aa (assoc 1 bb1 ))
		(setq aa1 (car aa))
		(setq aa2 (cdr aa))
		(setq di (atoi aa2))
		(setq dii (+ di 50))
		(memb)
		))
  ))
