(defun c:antt()
(setq IP (getpoint "\nPick the point:-"))
(command "_insert" "c:/detail/AANT" "@" "" "" "" ) (command "erase" "l" "")
(command "style" "WMF-Verdana0" "Verdana" "30" "1" "" "" "")
(setq P1t (polar IP (DTR 0.0) 320.52))
(setq P1 (polar P1t (DTR 270.0) 53.4))
(setq P2t (polar IP (DTR 0.0) 320.52))
(setq P2 (polar P2t (DTR 270.0) 152.88))
(setq P3t (polar IP (DTR 0.0) 795.92))
(setq P3 (polar P3t (DTR 270.0) 171.35))
(setq P4t (polar IP (DTR 0.0) 1429.62))
(setq P4 (polar P4t (DTR 270.0) 176.02))
(setq P5t (polar IP (DTR 0.0) 506.25))
(setq P5 (polar P5t (DTR 270.0) 483.99))
(setq P6t (polar IP (DTR 0.0) 506.25))
(setq P6 (polar P6t (DTR 270.0) 543.91))
(setq P7t (polar IP (DTR 0.0) 506.25))
(setq P7 (polar P7t (DTR 270.0) 601.83))
(setq P8t (polar IP (DTR 0.0) 506.25))
(setq P8 (polar P8t (DTR 270.0) 658.75))
(setq P9t (polar IP (DTR 0.0) 506.25))
(setq P9 (polar P9t (DTR 270.0) 723.67))
(setq P10t (polar IP (DTR 0.0) 496.98))
(setq P10 (polar P10t (DTR 270.0) 784.71))
(setq P11t (polar IP (DTR 0.0) 764.61))
(setq P11 (polar P11t (DTR 270.0) 483.99))
(setq P12t (polar IP (DTR 0.0) 945.87))
(setq P12 (polar P12t (DTR 270.0) 543.91))
(setq P13t (polar IP (DTR 0.0) 1159.58))
(setq P13 (polar P13t (DTR 270.0) 601.83))
(setq P14t (polar IP (DTR 0.0) 1347.93))
(setq P14 (polar P14t (DTR 270.0) 658.75))
(setq P15t (polar IP (DTR 0.0) 1522.09))
(setq P15 (polar P15t (DTR 270.0) 723.67))
(setq P16t (polar IP (DTR 0.0) 1695.22))
(setq P16 (polar P16t (DTR 270.0) 723.67))
(setq P17t (polar IP (DTR 0.0) 683.44))
(setq P17 (polar P17t (DTR 270.0) 879.46))
(command "TEXT" P1 "0" "25.354310")
(command "TEXT" P2 "0" "82.825900")
(command "TEXT" P3 "0" "170")
(command "TEXT" P4 "0" "FLAT")
(command "TEXT" P5 "0" (rtos 1.04 2 3))
(command "TEXT" P6 "0" (rtos 0.78 2 3))
(command "TEXT" P7 "0" (rtos 1.04 2 3))
(command "TEXT" P8 "0" (rtos 2.55 2 3))
(command "TEXT" P9 "0" (rtos 3.172 2 3))
(command "TEXT" P10 "0" (rtos 8.582* 2 3))
(command "TEXT" P11 "0" "10")
(command "TEXT" P12 "0" "11")
(command "TEXT" P13 "0" "12")
(command "TEXT" P14 "0" "13")
(command "TEXT" P15 "0" "14")
(command "TEXT" P16 "0" "15")
(command "TEXT" P17 "0" "R/RL-2060244")
(command "_insert" "C:/detail/BLOCKS/ANTE" IP "" "" "" )
)
(defun c:ttb()
(setq IP (getpoint "\nPick the point:-"))
(command "style" "ROMANS" "romans" "30" "1" "" "" "")
(setq tb1t (polar IP (DTR 180.0) 2275.09))
(setq tb1 (polar tb1t (DTR 90.0) 1444.17))
(setq tb2t (polar IP (DTR 180.0) 2005.02))
(setq tb2 (polar tb2t (DTR 90.0) 1444.17))
(setq tb3t (polar IP (DTR 180.0) 1485.06))
(setq tb3 (polar tb3t (DTR 90.0) 1444.17))
(setq tb4t (polar IP (DTR 180.0) 564.38))
(setq tb4 (polar tb4t (DTR 90.0) 1444.17))
(setq tb5t (polar IP (DTR 180.0) 307.72))
(setq tb5 (polar tb5t (DTR 90.0) 1444.17))
(setq tb6t (polar IP (DTR 180.0) 2042.81))
(setq tb6 (polar tb6t (DTR 90.0) 548))
(setq tb7t (polar IP (DTR 180.0) 2101.96))
(setq tb7 (polar tb7t (DTR 90.0) 446.91))
(setq tb8t (polar IP (DTR 180.0) 699.76))
(setq tb8 (polar tb8t (DTR 90.0) 451))
(setq tb9t (polar IP (DTR 180.0) 572.99))
(setq tb9 (polar tb9t (DTR 90.0) 451))
(setq tb10t (polar IP (DTR 180.0) 1871.81))
(setq tb10 (polar tb10t (DTR 90.0) 361.08))
(setq tb11t (polar IP (DTR 180.0) 1161.54))
(setq tb11 (polar tb11t (DTR 90.0) 360.22))
(setq tb12t (polar IP (DTR 180.0) 460.73))
(setq tb12 (polar tb12t (DTR 90.0) 361.08))
(setq tb13t (polar IP (DTR 180.0) 1871.81))
(setq tb13 (polar tb13t (DTR 90.0) 271.08))
(setq tb14t (polar IP (DTR 180.0) 1155.09))
(setq tb14 (polar tb14t (DTR 90.0) 271.08))
(setq tb15t (polar IP (DTR 180.0) 460.73))
(setq tb15 (polar tb15t (DTR 90.0) 271.08))
(setq tb16t (polar IP (DTR 180.0) 1871.07))
(setq tb16 (polar tb16t (DTR 90.0) 182.61))
(setq tb17t (polar IP (DTR 180.0) 1155.09))
(setq tb17 (polar tb17t (DTR 90.0) 181.08))
(setq tb18t (polar IP (DTR 180.0) 460.73))
(setq tb18 (polar tb18t (DTR 90.0) 181.08))
(command "TEXT" tb1 "0" "12.10.17")
(command "TEXT" tb2 "0" "0")
(command "TEXT" tb3 "0" "INITIAL SUBMITION")
(command "TEXT" tb4 "0" "D S K")
(command "TEXT" tb5 "0" "T S")
(command "TEXT" tb7 "0" "IN-1100658/TRD")
(command "TEXT" tb8 "0" "1")
(command "TEXT" tb9 "0" "1")
(command "TEXT" tb10 "0" "IN-1100658")
(command "TEXT" tb11 "0" "----")
(command "TEXT" tb12 "0" "UP East")
(command "TEXT" tb13 "0" "0")
(command "TEXT" tb14 "0" "D S K")
(command "TEXT" tb15 "0" "12.10.17")
(command "TEXT" tb16 "0" "K T V R")
(command "TEXT" tb17 "0" "T S")
(command "TEXT" tb18 "0" "0")
(command "style" "ROMANS" "romans" "45" "1" "" "" "")
(command "TEXT" tb6 "0" "STRENGTHENING DRAWING FOR 40m 4L-Angular TOWER")
(command "style" "ROMANS" "romans" "30" "1" "" "" "")
)
