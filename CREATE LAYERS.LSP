(setq plotsty "rccdwg.ctb")
(defun dtr(x) (* (/ pi 180.0) x))
(defun rtd(x) (* (/ 180 pi) x))
(defun c:lay ()
	     (command "layer" "m" "mem" "c" "4" "" "")
	     (command "layer" "m" "des" "c" "1" "" "")
	     (command "layer" "m" "gus" "c" "3" "" "")
	     (command "layer" "m" "con" "c" "1" "" "")
	     (command "layer" "m" "dim" "c" "5" "" "")
	     (command "layer" "m" "len" "c" "2" "" "")
	     (command "layer" "m" "fab" "c" "2" "" "")
	     (command "layer" "m" "int" "c" "7" "" "")
	     (command "layer" "m" "bolt" "c" "6" "" "")
	     (command "layer" "m" "hatch" "c" "8" "" "")
	     (command "layer" "m" "bdes" "c" "6" "" "")
	     (command "layer" "m" "das" "c" "1" "" "lt" "dashed" "" "")
	     (command "layer" "m" "hid" "c" "1" "" "lt" "hidden" "" "")
	     (command "layer" "m" "cen" "c" "2" "" "lt" "center" "" "")
	     (command "layer" "s" "0" "")
)
