(defun c:tobb (/ a ts n index b1 b c d b2)
(command "layer" "m" "temp2" "c" "4" "" "lw" "0.2" "" "")
(command "layer" "set" "mem" "")
   (setvar "osmode" 0)
   (setvar "cmdecho" 0)
   (setq a (ssget))
   (command "_.chprop" a "" "_LA" "temp2" "")
   (setq a1 (ssget))
   (command "_.chprop" a1 "" "_LA" "temp2" "")
   (setq n (sslength a))
   (setq index 0 )
   (repeat n
      (setq b1 (entget (ssname a index)))
      (setq b2 (entget (ssname a1 index)))
      (setq index (1+ index))
      (setq b (assoc 0 b1 ))
      (if (= "TEXT" (cdr b))
	 (progn
	    (setq aa (cdr (assoc 1 b1 )))
		(setq aa2 (cdr (assoc 1 b2 )))
	    (setq p1 (cdr (assoc 10 b1 )))
		(setq numlength (strlen aa))
		(if (= numlength 1) (command "_insert" "f2x" p1 "" "" "" aa aa2 ""))
		(if (= numlength 2) (command "_insert" "f2x" p1 "" "" "" aa aa2 ""))
		(if (= numlength 3) (command "_insert" "f3x" p1 "" "" "" aa aa2 ""))
		(if (= numlength 4) (command "_insert" "f4x" p1 "" "" "" aa aa2 ""))
		(if (= numlength 5) (command "_insert" "f5x" p1 "" "" "" aa aa2 ""))
		(if (= numlength 6) (command "_insert" "f6x" p1 "" "" "" aa aa2 ""))
	 )
      )
   )
   (ssget "X" '((8 . "temp2")))
   (command "erase" "p" "")
(setvar "osmode" 111)
(princ)
)
