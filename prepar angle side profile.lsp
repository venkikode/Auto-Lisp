(setq plotsty "rccdwg.ctb")
(defun dtr(x) (* (/ pi 180.0) x))
(defun rtd(x) (* (/ 180 pi) x))

(defun c:angle()
  (setq bph1 nil)
  (setq bph2 nil)
  (setq bph3 nil)
  (setq bph4 nil)
  (setq bpv1 nil)
  (setq bpv2 nil)
  (setq bpv3 nil)
  (setq bpv4 nil)
  (setq r1 nil)
  (setq r2 nil)
  (setq cmd (getvar "cmdecho"))
  (SETVAR "CMDECHO" 0)
  (setq fw (getreal "\nFlange width :")
       thk (getreal "\nThickness :")
	p2 (getpoint "\nAngle start point :")
	p1 (polar p2 (/ pi 2.0) fw)
	p3 (polar p2 0 fw)
	p4 (polar p3 (/ pi 2.0) thk)
	p5 (polar p4 pi (- fw thk))
	p6 (list (car p5) (cadr p1))
	
  )
  (if (= fw 45) (progn (setq r1 5.5) (setq r2 3.0)(init)))
  (if (= fw 50) (progn (setq r1 6.0) (setq r2 3.0)(init)))
  (if (= fw 55) (progn (setq r1 6.5) (setq r2 4.0)(init)))
  (if (= fw 60) (progn (setq r1 6.5) (setq r2 4.5)(init)))
  (if (= fw 65) (progn (setq r1 6.5) (setq r2 4.0)(init)))
  (if (= fw 70) (progn (setq r1 7.0) (setq r2 4.5)(init)))  
  (if (= fw 75) (progn (setq r1 7.0) (setq r2 4.5)(init)))
  (if (= fw 80) (progn (setq r1 8.0) (setq r2 4.5)(init)))
  (if (= fw 90) (progn (setq r1 8.5) (setq r2 5.5)(init)))
  (if (= fw 100) (progn (setq r1 8.5) (setq r2 5.5) (init)))
  (if (= fw 110) (progn (setq r1 10.0) (setq r2 6.0) (init)))
  (if (= fw 120) (progn (setq r1 10.0) (setq r2 6.0) (init)))
  (if (= fw 130) (progn (setq r1 10.0) (setq r2 6.0) (init)))
  (if (= fw 150) (progn (setq r1 12.0) (setq r2 8.0) (init)))
  (if (= fw 180) (progn (setq r1 15.0) (setq r2 10.0) (init)))
  (if (= fw 200) (progn (setq r1 15.0) (setq r2 10.0) (init)))
  (command "line" p1 p2 p3 p4 p5 p6 "c")
  (command "fillet" "r" r1)
  (command "fillet" "c" (polar p5 (dtr 135) 2) 
			  (polar p5 (dtr 315) 2))
  (command "fillet" "r" r2)
  (command "fillet" "c" (polar p4 (dtr 135) 2) 
			  (polar p4 (dtr 315) 2))
  (command "fillet" "r" r2)
  (command "fillet"  "c" (polar p6 (dtr 135) 2)
				 (polar p6 (dtr 315) 2))
  (command "pedit" "l" "" "j" "c" (polar p2 (dtr 225) 2)
			     (polar p2 (dtr 45) (+ (* fw (sqrt 2)) 2)) "" "") 
 
 
  (if (= sd "S") 
     (progn
       (command "line" bph1 bph2 "")
       (command "line" bpv1 bpv2 "")
     )  
  )
  (if (= sd "D") 
     (progn
       (command "line" bph1 bph2 "")
       (command "line" bph3 bph4 "")
       (command "line" bpv1 bpv2 "")
       (command "line" bpv3 bpv4 "")
     )  
  )
  (setvar "filletrad" 0)
  (SETVAR "CMDECHO" cmd)
)
