;;============AUTO PDF===================;;

(defun c:auttoh()
(defun dtr(x) (* (/ pi 180.0) x))
(command "zoom" "object" "all" "") 
(command "move" "all" "" (getvar "extmin") '(0 0))
(if (= printnumber nil) (setq printnumber 0))
(setq printnumber (1+ printnumber))
(setq filepath (getvar "dwgprefix"))
(setq tempfile (substr (strcat "" (getvar "dwgname")) 1 (- (strlen (getvar "dwgname")) 4)))
(setq filename (strcat filepath tempfile ".pdf"))
(setq printpoint '(0.0 0.0 0.0))

;(setq filename (getstring "\nEnter the file name"))
(setq hp1 (polar printpoint (dtr 0.0) 8910))
(setq hp2 (polar hp1 (dtr 90.0) 6300))
(command "_plot" "y" "model" "DWG To PDF.pc5" "ISO A4 (297.00 x 210.00 MM)" "m" "l" "n" "w" printpoint hp2 "fit" "c" "y" "rccdwg.ctb" "n" "a" filename "n" "y")
(princ) )

(defun c:auttov()
 (defun dtr(x) (* (/ pi 180.0) x))
 (command "zoom" "object" "all" "") 
(command "move" "all" "" (getvar "extmin") '(0 0))
(if (= printnumber nil) (setq printnumber 0))
(setq printnumber (1+ printnumber))
(setq filepath (getvar "dwgprefix"))
(setq tempfile (substr (strcat "" (getvar "dwgname")) 1 (- (strlen (getvar "dwgname")) 4)))
(setq filename (strcat filepath tempfile ".pdf"))
(setq printpoint '(0.0 0.0 0.0))
;(setq filename (getstring "\nEnter the file name"))
(setq hp1 (polar printpoint (dtr 0.0) 4455))
(setq hp2 (polar hp1 (dtr 90.0) 6300))
(command "_plot" "y" "model" "DWG To PDF.pc5" "ISO A4 (210.00 x 297.00 MM)" "m" "p" "n" "w" printpoint hp2 "fit" "c" "y" "rccdwg.ctb" "n" "a" filename "n" "y")
(princ) )

;===============================================;
(defun c:shoot()
(setq opt (getint "\nEnter the value for print (ex:21 [vertical (1) and horizantal(2)]:: "))
(defun dtr(x) (* (/ pi 180.0) x))
(setq printnumber 0)
(command "zoom" "object" "all" "") 
(command "move" "all" "" (getvar "extmin") '(0 0))
(setq printpoint '(0.0 0.0 0.0))

(defun h()
(defun dtr(x) (* (/ pi 180.0) x))
(if (= printnumber nil) (setq printnumber 0))
(setq printnumber (1+ printnumber))
(setq filepath (getvar "dwgprefix"))
(setq tempfile (substr (strcat "" (getvar "dwgname")) 1 (- (strlen (getvar "dwgname")) 4)))
(setq filename (strcat filepath tempfile "_" (itoa printnumber ) ".pdf"))
(setq hp1 (polar printpoint (dtr 0.0) 8910))
(setq hp2 (polar hp1 (dtr 90.0) 6300))
(command "_plot" "y" "model" "DWG To PDF.pc5" "ISO A4 (297.00 x 210.00 MM)" "m" "l" "n" "w" printpoint hp2 "fit" "c" "y" "rccdwg.ctb" "n" "a" filename "n" "y")
(princ)
(setq tp (polar printpoint (dtr 0.0) 9410))
(setq printpoint tp)
)
(defun v()
(defun dtr(x) (* (/ pi 180.0) x))
(if (= printnumber nil) (setq printnumber 0))
(setq printnumber (1+ printnumber))
(setq filepath (getvar "dwgprefix"))
(setq tempfile (substr (strcat "" (getvar "dwgname")) 1 (- (strlen (getvar "dwgname")) 4)))
(setq filename (strcat filepath tempfile "-" (itoa printnumber ) ".pdf"))
(setq hp1 (polar printpoint (dtr 0.0) 4455))
(setq hp2 (polar hp1 (dtr 90.0) 6300))
(command "_plot" "y" "model" "DWG To PDF.pc5" "ISO A4 (210.00 x 297.00 MM)" "m" "p" "n" "w" printpoint hp2 "fit" "c" "y" "rccdwg.ctb" "n" "a" filename "n" "y")
(princ)
(setq tp (polar printpoint (dtr 0.0) 4955))
(setq printpoint tp))

(if (= opt 1) (v) )
(if (= opt 2) (h))
(if (= opt 22) (polar (h) (h) ))
(if (= opt 222) (polar (h) (h) (h) ))
(if (= opt 2222) (polar (h) (h) (h) (h) ))
(if (= opt 22222) (polar (h) (h) (h) (h) (h) ))
(if (= opt 222222) (polar (h) (h) (h) (h) (h) (h) ))
(if (= opt 2222222) (polar (h) (h) (h) (h) (h) (h) (h) ))
(if (= opt 22222222) (polar (h) (h) (h) (h) (h) (h) (h) (h) ))
(if (= opt 222222222) (polar (h) (h) (h) (h) (h) (h) (h) (h) (h) ))
(if (= opt 2222222222) (polar (h) (h) (h) (h) (h) (h) (h) (h) (h) (h) ))

(if (= opt 21) (polar (h) (v) ))
(if (= opt 212) (polar (h) (v) (h) ))
(if (= opt 221) (polar (h) (h) (v) ))

(if (= opt 2122) (polar (h) (v) (h) (h) ))
(if (= opt 2212) (polar (h) (h) (v) (h) ))
(if (= opt 2221) (polar (h) (h) (h) (v) ))

(if (= opt 21222) (polar (h) (v) (h) (h) (h) ))
(if (= opt 22122) (polar (h) (h) (v) (h) (h) ))
(if (= opt 22212) (polar (h) (h) (h) (v) (h) ))
(if (= opt 22221) (polar (h) (h) (h) (h) (v) ))

(if (= opt 212222) (polar (h) (v) (h) (h) (h) (h) ))
(if (= opt 221222) (polar (h) (h) (v) (h) (h) (h) ))
(if (= opt 222122) (polar (h) (h) (h) (v) (h) (h) ))
(if (= opt 222212) (polar (h) (h) (h) (h) (v) (h) ))
(if (= opt 222221) (polar (h) (h) (h) (h) (h) (v) ))

(if (= opt 2122222) (polar (h) (v) (h) (h) (h) (h) (h) ))
(if (= opt 2212222) (polar (h) (h) (v) (h) (h) (h) (h) ))
(if (= opt 2221222) (polar (h) (h) (h) (v) (h) (h) (h) ))
(if (= opt 2222122) (polar (h) (h) (h) (h) (v) (h) (h) ))
(if (= opt 2222212) (polar (h) (h) (h) (h) (h) (v) (h) ))
(if (= opt 2222221) (polar (h) (h) (h) (h) (h) (h) (v) ))
(if (= opt 21222222) (polar (h) (h) (h) (h) (h) (h) (h) (h) ))
(if (= opt 22122222) (polar (h) (h) (h) (h) (h) (h) (h) (h) ))
(if (= opt 22212222) (polar (h) (h) (h) (h) (h) (h) (h) (h) ))
(if (= opt 22221222) (polar (h) (h) (h) (h) (h) (h) (h) (h) ))
(if (= opt 22222122) (polar (h) (h) (h) (h) (h) (h) (h) (h) ))
(if (= opt 22222212) (polar (h) (h) (h) (h) (h) (h) (h) (h) ))
(if (= opt 22222221) (polar (h) (h) (h) (h) (h) (h) (h) (h) ))
(if (= opt 212222222) (polar (h) (h) (h) (h) (h) (h) (h) (h) (h) ))
(if (= opt 221222222) (polar (h) (h) (h) (h) (h) (h) (h) (h) (h) ))
(if (= opt 222122222) (polar (h) (h) (h) (h) (h) (h) (h) (h) (h) ))
(if (= opt 222212222) (polar (h) (h) (h) (h) (h) (h) (h) (h) (h) ))
(if (= opt 222221222) (polar (h) (h) (h) (h) (h) (h) (h) (h) (h) ))
(if (= opt 222222122) (polar (h) (h) (h) (h) (h) (h) (h) (h) (h) ))
(if (= opt 222222212) (polar (h) (h) (h) (h) (h) (h) (h) (h) (h) ))
(if (= opt 222222221) (polar (h) (h) (h) (h) (h) (h) (h) (h) (h) ))
(if (= opt 2122222222) (polar (h) (h) (h) (h) (h) (h) (h) (h) (h) (h) ))
(if (= opt 2212222222) (polar (h) (h) (h) (h) (h) (h) (h) (h) (h) (h) ))
(if (= opt 2221222222) (polar (h) (h) (h) (h) (h) (h) (h) (h) (h) (h) ))
(if (= opt 2222122222) (polar (h) (h) (h) (h) (h) (h) (h) (h) (h) (h) ))
(if (= opt 2222212222) (polar (h) (h) (h) (h) (h) (h) (h) (h) (h) (h) ))
(if (= opt 2222221222) (polar (h) (h) (h) (h) (h) (h) (h) (h) (h) (h) ))
(if (= opt 2222222122) (polar (h) (h) (h) (h) (h) (h) (h) (h) (h) (h) ))
(if (= opt 2222222212) (polar (h) (h) (h) (h) (h) (h) (h) (h) (h) (h) ))
(if (= opt 2222222221) (polar (h) (h) (h) (h) (h) (h) (h) (h) (h) (h) ))
)
