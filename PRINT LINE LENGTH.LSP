(setq plotsty "rccdwg.ctb")
(defun dtr(x) (* (/ pi 180.0) x))
(defun rtd(x) (* (/ 180 pi) x))

(defun c:LL1 (/ a ts n index b1 b c d b2)
   (setq a (ssget))
   (setq n (sslength a))
   (setq index 0 )
   (setq p6 (getpoint "\npick the point to generate line lengths: "))
   (repeat n
      (setq b1 (entget (ssname a index)))
      (setq index (1+ index))
      (setq b (assoc 0 b1 ))
      (if (= "LINE" (cdr b))
	 (progn
	    (setq c (assoc 10 b1 ))
		(setq cc (assoc 11 b1 ))
		(setq p1 (cdr c))
        (setq p2 (cdr cc))
	    (setq di (distance p1 p2))
		(setq ang (angle p1 p2))
		(setq p3 (/ di 2))
		(setq p4 (polar p1 (angle p1 p2) p3))
		(setq p5 (polar p4 (+ ang (dtr 90.0)) 20))
		(setq dis (fix di))
		(if (< (rtd ang) 90) (setq angg (- (rtd ang) 360)))
        (if (> (rtd ang) 90) (setq angg (- (rtd ang) 180)))
		(setq nn index)
        (setq sn (strcat "N" (itoa nn )))
		(command "TEXT" p5 angg sn "")
	    (setq p7 (polar p6 (dtr 270.0) 100))
		(setq p8 (polar p7 (dtr 0.0) 150))
		(command "TEXT" p7 "0" sn "")(command "TEXT" p8 "0" dis "")
		(setq p6 p7)
	 )
      )
   )
 (princ)
)
