(defun c:dtc()
(setq a (ssget))
   (setq n (sslength a))
   (setq index 0 )
   (repeat n
      (setq b (entget (ssname a index)))
      (setq index (1+ index))
      	(setq c (assoc 42 b ))
		(setq d (assoc 1 b ))
		(setq c1 (car c))
		(setq c2 (cdr c))
		(setq d1 (car d))
		(setq d2 (cdr d))
		(setq new (cons d1 c2))
		(setq b (subst new d b))
	    (entmod b) 
		  )
		  )
		  
(defun c:dtc1()
(setq a1 (entsel "select the obj")
       a (entget a1)) 
      	(setq c (assoc 42 a ))
		(setq c2 (cdr c))
		(command "dim1" "new" c2  a "")
				  )
