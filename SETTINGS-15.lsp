(defun c:SETTINGS()
  (setq sf (getreal "\nEnter scale factor :"))
  (command "dimscale" sf)
  (command "style" "arial" "arial" (* 4.0 sf) "" "" "" "")
  (command "style" "standard" "simplex" (* 2.5 sf) "0.8" "" "" "" "")
  (command "style" "SHX_style" "simplex" (* 2.5 sf) "0.8" "" "" "" "")
  (command "ltscale" (* 5.0 sf))
  (command "dimasz" 2.5)
  (command "dimtsz" 0.5)
  (command "dimtxt" 2.5)
  (command "dimexe" 1)
  (command "dimexo" 1)
  (command "dimlwd" 9)
  (command "dimlwe" 9)
  (command "dimgap" 1)
  (command "dimtad" 1)
  (command "dimtofl" 1)
  (command "dimtih" 0)
  (command "dimtoh" 0)
  (command "layer" "m" "mem" "c" "4" "" "lw" "0.2" "" "")
  (command "layer" "m" "des" "c" "1" "" "lw" "0.09" "" "")
  (command "layer" "m" "gus" "c" "3" "" "lw" "0.2" "" "")
  (command "layer" "m" "con" "c" "1" "" "lw" "0.09" "" "")
  (command "layer" "m" "dim" "c" "2" "" "lw" "0.2" "" "")
  (command "dimlwd" 9) (command "dimlwe" 9)
  (command "layer" "m" "text" "c" "2" "" "lw" "0.2" "" "")
  (command "layer" "m" "bolt" "c" "4" "" "lw" "0.2" "" "")
  (command "layer" "m" "bdes" "c" "31" "" "lw" "0.2" "" "")
  (command "layer" "m" "das" "c" "1" "" "lt" "HIDDEN" "" "lw" "0.09" "" "")
  (command "layer" "m" "cen" "c" "2" "" "lt" "center" "" "lw" "0.09" "" "")
  (command "layer" "m" "cen1" "c" "31" "" "lt" "center" "" "lw" "0.09" "" "")
  (command "layer" "s" "0" "")
)
